module engineer_types {
    yang-version 1.1;
    namespace "urn:bell.ca:devexperts:types";
    prefix "types";
    revision 2021-04-14;
    typedef age_type {
        description "Engineers start work at 18 and should be retired by 110";
        type int8 {
            range "18 .. 110";
        }
        units years;
    }
    typedef transportation_type {
        description "Method of transportation";
        type enumeration {
            enum foot;
            enum bicycle;
            enum car;
            enum bus;
            enum train;
            enum boat;
            enum aeroplane;
        }
    }
}
